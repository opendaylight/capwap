module wtpdiscover-impl {
    yang-version 1;
    namespace "urn:opendaylight:capwap:wtpdiscover-impl";
    prefix "wtpdiscover-impl";

    import config { prefix config; revision-date 2013-04-05; }
    import opendaylight-md-sal-binding { prefix mdsal; revision-date 2013-10-28;}

    description
        "Service definition for wtpdiscover project";

    revision "2014-12-10" {
        description
            "Initial revision";
    }

    identity wtpdiscover {
        base config:module-type;
        config:java-name-prefix Wtpdiscover;
    }

    augment "/config:modules/config:module/config:configuration" {
        case wtpdiscover {
            when "/config:modules/config:module/config:type = 'wtpdiscover'";
            container notification-service {
                uses config:service-ref {
                    refine type {
                        mandatory true;
                        config:required-identity mdsal:binding-notification-service;
                    }
                }
            }
        }
    }
}
