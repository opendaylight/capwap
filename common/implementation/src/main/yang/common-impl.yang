module common-impl {
    yang-version 1;
    namespace "urn:opendaylight:capwap:common-impl";
    prefix "common-impl";

    import config { prefix config; revision-date 2013-04-05; }
    import opendaylight-md-sal-binding { prefix mdsal; revision-date 2013-10-28;}

    description
        "Service definition for common project";

    revision "2014-12-10" {
        description
            "Initial revision";
    }

    identity common {
        base config:module-type;
        config:java-name-prefix Common;
    }

    augment "/config:modules/config:module/config:configuration" {
        case common {
            when "/config:modules/config:module/config:type = 'common'";
            container notification-service {
                uses config:service-ref {
                    refine type {
                        mandatory true;
                        config:required-identity mdsal:binding-notification-service;
                    }
                }
            }
        }
    }
}
