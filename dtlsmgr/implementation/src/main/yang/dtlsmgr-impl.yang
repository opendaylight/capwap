module dtlsmgr-impl {
    yang-version 1;
    namespace "urn:opendaylight:capwap:dtlsmgr-impl";
    prefix "dtlsmgr-impl";

    import config { prefix config; revision-date 2013-04-05; }
    import opendaylight-md-sal-binding { prefix mdsal; revision-date 2013-10-28;}

    description
        "Service definition for dtlsmgr project";

    revision "2014-12-10" {
        description
            "Initial revision";
    }

    identity dtlsmgr {
        base config:module-type;
        config:java-name-prefix DTLSMgr;
    }

    augment "/config:modules/config:module/config:configuration" {
        case dtlsmgr {
            when "/config:modules/config:module/config:type = 'dtlsmgr'";
            container notification-service {
                uses config:service-ref {
                    refine type {
                        mandatory true;
                        config:required-identity mdsal:binding-notification-service;
                    }
                }
            }
        }
    }
}
