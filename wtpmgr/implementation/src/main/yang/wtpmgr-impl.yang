module wtpmgr-impl {
    yang-version 1;
    namespace "urn:opendaylight:capwap:wtpmgr-impl";
    prefix "wtpmgr-impl";

    import config { prefix config; revision-date 2013-04-05; }
    import opendaylight-md-sal-binding { prefix mdsal; revision-date 2013-10-28;}

    description
        "Service definition for wtpmgr project";

    revision "2014-12-10" {
        description
            "Initial revision";
    }

    identity wtpmgr {
        base config:module-type;
        config:java-name-prefix WtpMgr;
    }

    augment "/config:modules/config:module/config:configuration" {
        case wtpmgr {
            when "/config:modules/config:module/config:type = 'wtpmgr'";
            container notification-service {
                uses config:service-ref {
                    refine type {
                        mandatory true;
                        config:required-identity mdsal:binding-notification-service;
                    }
                }
            }
        }
    }
}
